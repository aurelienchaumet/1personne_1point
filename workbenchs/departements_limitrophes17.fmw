FME workspace departements_limitrophes17.fmw

Parameters:
- SourceDataset_SHAPEFILE = /Users/aurelienchaumet/Documents/Perso/Portfolio/1point_1personne/sig/sources/cadastre-france-communes-shp/communes.shp   # Source Esri Shapefile(s)
- DestDataset_SHAPEFILE = /Users/aurelienchaumet/Documents/Perso/Portfolio/1point_1personne/sig/resultats   # Destination Esri Shapefile Folder

Readers:
- SHAPEFILE_1: SHAPEFILE from $(SourceDataset_SHAPEFILE)

Writers:
- SHAPEFILE_2: SHAPEFILE to $(DestDataset_SHAPEFILE)

communes (reader SHAPEFILE_1)
    attributes: id char(5), nom char(80), created date, updated date
    -> AttributeManager
AttributeManager
    ATTR_TABLE = SET_TO dep = @Substring(@Value(id),0,2)
    -> Dissolver
Dissolver
    ACCUM_INPUT_ATTRS = Use Attributes From One Feature
    CLEANING_TOLERANCE = Automatic
    CONNECT_Z_MODE = First Wins
    DEAGGREGATE_INPUT = Yes
    GROUP_BY = dep
    AREA -> Tester
Tester
    BOOL_OP = OR
    COMPOSITE_TEST = 1 OR 2 OR 3 OR 4 OR 5 OR 6
    TEST_CLAUSE:
      TEST @Value(dep) = 17
      TEST @Value(dep) = 16
      TEST @Value(dep) = 33
      TEST @Value(dep) = 79
      TEST @Value(dep) = 85
      TEST @Value(dep) = 24
    TEST_MODE = TEST
    PASSED -> DonutHoleExtractor
DonutHoleExtractor
    DEAGGREGATE_INPUT = Yes
    OUTERSHELL -> Aggregator
Aggregator
    ACCUM_ATTRS_NAME = Use Attributes From One Feature
    AGGREGATE_TYPE = Homogeneous Collection (If Possible)
    GROUP_BY = dep
    MODE = Geometry - Assemble One Level
    SEP = ,
    AGGREGATE -> departements_limitrophes (writer SHAPEFILE_2)
departements_limitrophes (writer SHAPEFILE_2)
    attributes: id char(5), nom char(80), created date, updated date
